# /***************************************************************************
#  *                                                                         *
#  *   AI Context Export - FreeCAD macro                                     *
#  *                                                                         *
#  *   Builds a text snapshot of the current FreeCAD state (document tree,   *
#  *   sketch geometry and constraints, undo history, menu tree, available   *
#  *   commands) that can be pasted into any LLM chat together with a        *
#  *   question like "how do I make two lines share the same X?".            *
#  *                                                                         *
#  *   Install: copy into the FreeCAD user Macro directory                   *
#  *     (GUI: Macro > Macros... > User macros location)                     *
#  *   Run: Macro > Macros... > AIContextExport > Execute                    *
#  *                                                                         *
#  *   SPDX-License-Identifier: LGPL-2.1-or-later                            *
#  *                                                                         *
#  ***************************************************************************/

__Name__ = "AIContextExport"
__Comment__ = "Export model/history/menu context as text for an LLM chat"
__Author__ = "FreeCAD AI Assist experiment"
__Version__ = "0.3.1"
__License__ = "LGPL-2.1-or-later"

import sys

import FreeCAD as App

try:
    import FreeCADGui as Gui

    HAS_GUI = True
except ImportError:
    HAS_GUI = False

MAX_OBJECTS = 200
MAX_GEO_ITEMS = 100
MAX_CONSTRAINTS = 150
MAX_HISTORY = 60
MAX_MENU_ITEMS = 400
MAX_COMMANDS = 300
CHAR_BUDGET = 60000

# Compact mode keeps only menu branches relevant to modelling/sketching and
# only problem-relevant commands; "Full" mode includes everything.
COMPACT_TOP_MENUS = {"file", "edit", "sketch", "part", "part design", "draft", "modify"}
RELEVANT_CMD_PREFIXES = (
    "Sketcher_", "Draft_", "Part_", "PartDesign_",
    "Std_New", "Std_Open", "Std_Save", "Std_Undo", "Std_Redo",
    "Std_Delete", "Std_Duplicate", "Std_Transform", "Std_Placement",
)

CONSTRAINT_TYPES = [
    "Coincident", "Horizontal", "Vertical", "Parallel", "Perpendicular",
    "Tangent", "Distance", "DistanceX", "DistanceY", "Angle", "Radius",
    "Diameter", "Weight", "PointOnObject", "Equal", "Symmetric", "Block",
    "InternalAlignment", "SnellsLaw",
]

PREAMBLE = """\
# FreeCAD context snapshot
#
# This text was generated by the FreeCAD "AI Context Export" macro. It
# describes the current state of a FreeCAD session. The user will ask a
# question (before or after this block). Answer it using ONLY the
# FreeCAD concepts listed in the context below:
#
# - To guide the user: name the exact menu path (from the MENU TREE section)
#   or toolbar button (from the AVAILABLE COMMANDS section) to use.
# - For sketch problems: refer to geometry items by their [n] index and use
#   the constraint types from the CONSTRAINT CATALOGUE. Point positions:
#   1=start, 2=end, 3=mid, 0=not applicable. In the CURRENT SELECTION
#   section, a subelement like "Edge1" means sketch geometry [0], "Edge2"
#   means [1], etc. (1-based edge number = geometry index + 1).
# - If a section says something is missing (no sketch, nothing selected),
#   start your answer by telling the user how to create/select it - using
#   the menu paths from the MENU TREE section - before anything else.
# - Optionally give a Python snippet for the FreeCAD Python console, using
#   App.ActiveDocument, Sketcher.Constraint(...) and obj.recompute().
# - The MENU TREE and AVAILABLE COMMANDS sections are filtered to
#   modelling/sketching relevance; ignore anything not needed.
# FreeCAD version: {version}
"""


def _fmt(value, ndigits=3):
    if isinstance(value, float):
        return round(value, ndigits)
    return value


def _vec_str(v):
    if v is None:
        return "?"
    try:
        return "({:.3f}, {:.3f}, {:.3f})".format(v.x, v.y, v.z)
    except AttributeError:
        return str(v)


def _pos_name(pos):
    return {0: "none", 1: "start", 2: "end", 3: "mid"}.get(pos, "pos%s" % pos)


def _cut(text, limit):
    if len(text) <= limit:
        return text
    return text[:limit] + "\n... [truncated, original %s chars]" % len(text)


# ---------------------------------------------------------------------------
# Sections
# ---------------------------------------------------------------------------

def section_document_tree():
    lines = ["## DOCUMENT TREE"]
    docs = list(App.listDocuments().values())
    if not docs:
        lines.append("(no documents open)")
        return "\n".join(lines)
    count = 0
    truncated = False
    for doc in docs:
        lines.append("Document: %s (label: %s)" % (doc.Name, doc.Label))
        for obj in doc.Objects:
            if count >= MAX_OBJECTS:
                truncated = True
                break
            label = obj.Label if obj.Label != obj.Name else ""
            suffix = ' label="%s"' % label if label else ""
            lines.append("  %s%s - %s" % (obj.Name, suffix, obj.TypeId))
            count += 1
        if truncated:
            lines.append("  ... [%d more objects not shown]" % (len(doc.Objects) - count))
            break
    return "\n".join(lines)


def _describe_geometry(index, geo):
    try:
        if geo.TypeId == "Part::GeomLineSegment":
            return "[%d] LineSegment start=%s end=%s" % (
                index, _vec_str(geo.StartPoint), _vec_str(geo.EndPoint))
        if geo.TypeId == "Part::GeomCircle":
            return "[%d] Circle center=%s radius=%.3f" % (
                index, _vec_str(geo.Center), geo.Radius)
        if geo.TypeId == "Part::GeomArcOfCircle":
            return "[%d] ArcOfCircle center=%s radius=%.3f start_angle=%.3f end_angle=%.3f" % (
                index, _vec_str(geo.Center), geo.Radius, geo.FirstParameter, geo.LastParameter)
        if geo.TypeId == "Part::GeomPoint":
            return "[%d] Point %s" % (index, _vec_str(geo.Point))
    except AttributeError:
        pass
    return "[%d] %s" % (index, getattr(geo, "TypeId", type(geo).__name__))


def _describe_constraint(index, con):
    parts = ["[%d] %s" % (index, con.Type)]
    try:
        first = "geo%s" % con.First
        if con.FirstPos:
            first += "(%s)" % _pos_name(con.FirstPos)
        parts.append(first)
        if con.Second != -2000:
            second = "geo%s" % con.Second
            if con.SecondPos:
                second += "(%s)" % _pos_name(con.SecondPos)
            parts.append("to " + second)
        if con.Type in ("Distance", "DistanceX", "DistanceY", "Angle",
                        "Radius", "Diameter", "Weight"):
            parts.append("value=%s" % _fmt(con.Value))
        if not con.IsDriving:
            parts.append("reference-only")
    except AttributeError:
        pass
    return " ".join(parts)


def _pick_sketch(doc):
    """Return (sketch, note). Prefers the sketch being edited, then the
    selected sketch, then the last sketch of the active document, then the
    last sketch of any open doc."""
    if HAS_GUI:
        editing = _active_sketch_view()
        if editing is not None:
            return editing, "(this sketch is currently being edited)"
    if doc is not None:
        if HAS_GUI:
            try:
                for obj in Gui.Selection.getSelection(doc.Name):
                    if obj.isDerivedFrom("Sketcher::SketchObject"):
                        return obj, "(this sketch is currently selected)"
            except Exception:
                pass
        sketches = [o for o in doc.Objects if o.isDerivedFrom("Sketcher::SketchObject")]
        if sketches:
            return sketches[-1], None
    for other in App.listDocuments().values():
        sketches = [o for o in other.Objects if o.isDerivedFrom("Sketcher::SketchObject")]
        if sketches:
            return sketches[-1], ("(active document has no sketch; showing \"%s\" "
                                  "from document %s instead)" % (sketches[-1].Name, other.Name))
    return None, None


def section_sketch(doc):
    lines = ["## ACTIVE SKETCH (detailed)"]
    sketch, note = _pick_sketch(doc)
    if sketch is None:
        lines.append("(no sketch found in any open document - to create one: "
                     "File > New Document (Ctrl+N), then Sketch > Create sketch "
                     "(or press S in the Sketcher workbench), then re-run this macro)")
        return "\n".join(lines)
    if note:
        lines.append(note)
    lines.append("Sketch: %s (label: %s)" % (sketch.Name, sketch.Label))
    lines.append("Geometry (%d items):" % len(sketch.Geometry))
    for i, geo in enumerate(sketch.Geometry[:MAX_GEO_ITEMS]):
        construction = ""
        try:
            if sketch.getConstruction(i):
                construction = " [construction]"
        except Exception:
            pass
        lines.append("  " + _describe_geometry(i, geo) + construction)
    if len(sketch.Geometry) > MAX_GEO_ITEMS:
        lines.append("  ... [%d more geometry items]" % (len(sketch.Geometry) - MAX_GEO_ITEMS))
    lines.append("Constraints (%d):" % len(sketch.Constraints))
    for i, con in enumerate(sketch.Constraints[:MAX_CONSTRAINTS]):
        lines.append("  " + _describe_constraint(i, con))
    if len(sketch.Constraints) > MAX_CONSTRAINTS:
        lines.append("  ... [%d more constraints]" % (len(sketch.Constraints) - MAX_CONSTRAINTS))
    return "\n".join(lines)


def section_history(doc):
    lines = ["## EDIT HISTORY (oldest first)"]
    if doc is None:
        lines.append("(no active document)")
        return "\n".join(lines)
    try:
        names = list(doc.UndoNames)
    except Exception:
        lines.append("(history unavailable)")
        return "\n".join(lines)
    names = names[::-1]  # newest first -> chronological
    for name in names[:MAX_HISTORY]:
        lines.append("- %s" % name)
    if len(names) > MAX_HISTORY:
        lines.append("... [%d older steps omitted]" % (len(names) - MAX_HISTORY))
    if not names:
        lines.append("(no undoable steps - document unchanged or just opened)")
    return "\n".join(lines)


def _selection_ex():
    """Return list of (obj, [subelement names]) for the current selection."""
    result = []
    try:
        for ex in Gui.Selection.getSelectionEx("", 0):
            subs = list(ex.SubElementNames or [])
            result.append((ex.Object, subs))
    except Exception:
        try:
            for obj in Gui.Selection.getSelection():
                result.append((obj, []))
        except Exception:
            pass
    return result


def _active_sketch_view():
    """If a sketch is being edited, return its object."""
    try:
        view = Gui.ActiveDocument.ActiveView
        if hasattr(view, "getSketchObject"):
            sk = view.getSketchObject()
            if sk is not None:
                return sk
    except Exception:
        pass
    return None


def _describe_object_generic(obj, indent="  "):
    """Generic property/shape dump, useful in any workbench."""
    lines = []
    try:
        lines.append("%slabel=%s" % (indent, obj.Label))
        for prop in ("Placement", "Length", "Width", "Height", "Radius", "Angle"):
            if hasattr(obj, prop):
                lines.append("%s%s=%s" % (indent, prop, _fmt(getattr(obj, prop))))
        if hasattr(obj, "Shape") and obj.Shape is not None and not obj.Shape.isNull():
            sh = obj.Shape
            lines.append("%sShape type=%s edges=%d faces=%d vertexes=%d volume=%s"
                         % (indent, sh.ShapeType, len(sh.Edges), len(sh.Faces),
                            len(sh.Vertexes), _fmt(sh.Volume)))
            for i, e in enumerate(sh.Edges[:20]):
                curve = getattr(e.Curve, "TypeId", "?")
                start = getattr(e, "Vertexes", [None])
                try:
                    sv = e.Vertexes[0].Point
                    ev = e.Vertexes[-1].Point
                    lines.append("%sShape edge %d: %s from %s to %s length=%s"
                                 % (indent, i + 1, curve, _vec_str(sv), _vec_str(ev),
                                    _fmt(e.Length)))
                except Exception:
                    lines.append("%sShape edge %d: %s" % (indent, i + 1, curve))
    except Exception as exc:
        lines.append("%s(details unavailable: %s)" % (indent, exc))
    return lines


def section_selection():
    lines = ["## CURRENT SELECTION"]
    if not HAS_GUI:
        lines.append("(GUI not available)")
        return "\n".join(lines)
    sel = _selection_ex()
    if not sel:
        lines.append("(nothing selected - tip: select the sketch, edge or object "
                     "you want advice about before running this macro)")
        return "\n".join(lines)
    for obj, subs in sel:
        if subs:
            lines.append("- %s (%s), selected subelements: %s"
                         % (obj.Name, obj.TypeId, ", ".join(subs)))
        else:
            lines.append("- %s (%s)" % (obj.Name, obj.TypeId))
        lines.extend(_describe_object_generic(obj))
        if obj.isDerivedFrom("Sketcher::SketchObject"):
            lines.append("  (this is a sketch; see ACTIVE SKETCH section for details)")
    return "\n".join(lines)


def section_menu_tree(full=False):
    lines = ["## MENU TREE (clickable paths, format: Menu > Submenu > Item (shortcut))"]
    if not HAS_GUI:
        lines.append("(GUI not available)")
        return "\n".join(lines)
    if not full:
        lines.append("(filtered to modelling/sketching menus; other menus omitted)")
    try:
        from PySide import QtWidgets

        mw = Gui.getMainWindow()
        bar = mw.menuBar()
    except Exception:
        lines.append("(menu bar not available)")
        return "\n".join(lines)

    count = 0

    def walk(action, depth, max_depth=2):
        nonlocal count
        if count >= MAX_MENU_ITEMS:
            return
        menu = action.menu()
        text = action.text().replace("&", "")
        if not text:
            return
        indent = "  " * depth
        if menu is None:
            shortcut = action.shortcut().toString()
            suffix = " (%s)" % shortcut if shortcut else ""
            lines.append("%s- %s%s" % (indent, text, suffix))
            count += 1
        else:
            lines.append("%s+ %s" % (indent, text))
            count += 1
            if depth < max_depth:
                for child in menu.actions():
                    walk(child, depth + 1, max_depth)

    def walk_all(root_actions, max_depth=2):
        for action in root_actions:
            walk(action, 0, max_depth)

    matched = []
    for action in bar.actions():
        top = action.text().replace("&", "").strip().lower()
        if not full and top in COMPACT_TOP_MENUS:
            matched.append(action)
        elif full:
            matched.append(action)
    if matched:
        walk_all(matched)
    if not matched or not lines[1:]:
        # nothing matched the compact filter -> fall back to shallow full dump
        del lines[1:]
        walk_all(bar.actions(), max_depth=1)
        lines.insert(1, "(no modelling menus found; showing top-level menus only)")
    if count >= MAX_MENU_ITEMS:
        lines.append("... [menu tree truncated at %d entries]" % MAX_MENU_ITEMS)
    return "\n".join(lines)


def section_commands(full=False):
    lines = ["## AVAILABLE COMMANDS"]
    if not HAS_GUI:
        lines.append("(GUI not available)")
        return "\n".join(lines)
    try:
        wb = Gui.activeWorkbench()
        if wb is not None:
            wb_name = wb.name() if hasattr(wb, "name") else getattr(wb, "Name", "?")
    except Exception:
        wb_name = "?"
    lines.append("Active workbench: %s" % wb_name)
    try:
        names = list(Gui.listCommands())
    except Exception:
        lines.append("(command list not available)")
        return "\n".join(lines)
    lines.append("Command count: %d" % len(names))
    if not full:
        relevant = sorted(n for n in names if n.startswith(RELEVANT_CMD_PREFIXES))
        lines.append("(filtered to modelling/sketching commands; %d of %d shown)"
                     % (len(relevant), len(names)))
        lines.append("Commands: %s" % ", ".join(relevant[:MAX_COMMANDS]))
        if len(relevant) > MAX_COMMANDS:
            lines.append("... [%d more commands]" % (len(relevant) - MAX_COMMANDS))
    else:
        lines.append("Commands: %s" % ", ".join(sorted(names)[:MAX_COMMANDS]))
        if len(names) > MAX_COMMANDS:
            lines.append("... [%d more commands]" % (len(names) - MAX_COMMANDS))
    lines.append("(menu paths for these are in the MENU TREE section)")
    return "\n".join(lines)


def section_catalogue():
    lines = ["## CONSTRAINT CATALOGUE (Sketcher.Constraint types)"]
    lines.append(", ".join(CONSTRAINT_TYPES))
    lines.append("Usage: Sketcher.Constraint(type, first, firstPos, second, secondPos, value)")
    return "\n".join(lines)


# ---------------------------------------------------------------------------
# Assembly
# ---------------------------------------------------------------------------

def build_context(full=False):
    doc = App.ActiveDocument
    sections = [
        PREAMBLE.format(version=".".join(App.Version()[:3])),
        "--- SYSTEM CONTEXT ---",
        section_document_tree(),
        section_selection(),
        section_sketch(doc),
        section_history(doc),
        section_menu_tree(full),
        section_commands(full),
        section_catalogue(),
        "--- END OF SYSTEM CONTEXT ---",
    ]
    text = "\n\n".join(s for s in sections if s)
    return _cut(text, CHAR_BUDGET)


def _show_error(exc):
    """Popup with the traceback so failures are never silent."""
    import traceback

    text = "".join(traceback.format_exception(exc))
    sys.stderr.write("AIContextExport failed:\n" + text)
    try:
        from PySide import QtWidgets

        box = QtWidgets.QMessageBox(Gui.getMainWindow())
        box.setIcon(QtWidgets.QMessageBox.Critical)
        box.setWindowTitle("AI Context Export - error")
        box.setText("Macro failed - the context was NOT copied. Please report this text:")
        box.setDetailedText(text)
        box.show()
    except Exception:
        pass


def main():
    if not HAS_GUI:
        print(build_context())
        return
    try:
        from PySide import QtGui, QtWidgets
    except ImportError:
        from PySide6 import QtGui, QtWidgets

    try:
        text = build_context()
    except Exception as exc:
        _show_error(exc)
        return

    # put the context on the clipboard immediately, so even if the dialog
    # fails or is closed unexpectedly, the paste step works
    clipboard = QtGui.QApplication.clipboard()
    clipboard.setText(text, QtGui.QClipboard.Clipboard)

    mw = Gui.getMainWindow()
    dlg = mw.findChild(QtWidgets.QDialog, "AIContextExportDialog")

    if dlg is not None:
        # guard against stale dialogs from older macro versions that lack
        # the expected children - discard and rebuild in that case
        view = dlg.findChild(QtWidgets.QPlainTextEdit, "AIContextExportText")
        full_cb = dlg.findChild(QtWidgets.QCheckBox, "AIContextExportFull")
        if view is None or full_cb is None:
            dlg.deleteLater()
            dlg = None

    if dlg is None:
        state = {"full": False, "text": text}
        dlg = QtWidgets.QDialog(mw)
        dlg.setObjectName("AIContextExportDialog")
        dlg.setWindowTitle("AI Context Export")
        dlg.resize(720, 560)
        layout = QtWidgets.QVBoxLayout(dlg)
        full_cb = QtWidgets.QCheckBox("Full context (all menus and all commands)")
        full_cb.setObjectName("AIContextExportFull")
        layout.addWidget(full_cb)
        view = QtWidgets.QPlainTextEdit()
        view.setObjectName("AIContextExportText")
        view.setReadOnly(True)
        view.setPlainText(state["text"])
        view.setLineWrapMode(QtWidgets.QPlainTextEdit.NoWrap)
        font = QtGui.QFontDatabase.systemFont(QtGui.QFontDatabase.FixedFont)
        view.setFont(font)
        layout.addWidget(view)
        buttons = QtWidgets.QHBoxLayout()
        copy_btn = QtWidgets.QPushButton("Copy to clipboard")
        close_btn = QtWidgets.QPushButton("Close")
        buttons.addStretch()
        buttons.addWidget(copy_btn)
        buttons.addWidget(close_btn)
        layout.addLayout(buttons)

        def rebuild(full):
            try:
                state["full"] = full
                state["text"] = build_context(full)
                view.setPlainText(state["text"])
            except Exception as exc:
                _show_error(exc)

        def do_copy():
            QtGui.QApplication.clipboard().setText(state["text"])

        def on_toggle(checked):
            rebuild(bool(checked))

        full_cb.stateChanged.connect(on_toggle)
        copy_btn.clicked.connect(do_copy)
        close_btn.clicked.connect(dlg.close)
    else:
        # existing dialog with expected children - just refresh its content
        view = dlg.findChild(QtWidgets.QPlainTextEdit, "AIContextExportText")
        full_cb = dlg.findChild(QtWidgets.QCheckBox, "AIContextExportFull")
        try:
            view.setPlainText(build_context(bool(full_cb.checkState())))
        except Exception as exc:
            _show_error(exc)
    dlg.show()
    dlg.raise_()


if __name__ == "__main__":
    main()
